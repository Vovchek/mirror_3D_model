# FreeCAD macro: generate puck-shaped part with flats, radial blind holes, chamfers (facets), and notches
# Usage: run this as a macro inside FreeCAD (Macro -> Macros... -> Create, paste and Run)
# Fix: ensure flat-cut boxes lie on the *outside* of the cutting plane so subtracting them removes the lateral chips
# (leaving the main puck body). This is done by placing the box so its max-local-Y face sits on the plane
# when the box's local-Y axis points inward; equivalently we shift the local origin by +n*box_thickness when
# local-Y points inward, so the box occupies the outside region.

import FreeCAD
import Part
from FreeCAD import Base
import math

# Ensure there is an active document
DOC = FreeCAD.ActiveDocument
if DOC is None:
    DOC = FreeCAD.newDocument("PuckDoc")

# -------------------- PARAMETERS (edit these as needed) --------------------
Code = "C-M9"  # part code for naming
outer_diameter = 430.0
radius = outer_diameter / 2.0
height = 60.99
Tc = 60.0
Rc = 22191.9

# Flats adjustent to holes (three) - distances and angles (degrees)
flat_holes_distance_from_center = 212.0
flat_holes_angles_deg = [30, 150, 270]
flat_holes_length = 2*(radius**2 - flat_holes_distance_from_center**2)**0.5

# Blind holes (from generatrix towards center)
hole_diameter = 10.0
hole_depth = 15.0
hole_angles_deg = [30, 150, 270]

# Flats marked 'Critical Zone' (three) - distances and angles (degrees)
flat_critical_distance_from_center = 210.0
flat_critical_angles_deg = [90, 210, 330]
flat_critical_length = 2*(radius**2 - flat_critical_distance_from_center**2)**0.5

# Facet (approximation using fillet)
facet_leg = 5.0

# Notches (right-angled dents)
notch_angles = [0, 180]
notch_depth = 1.0
# NOTE: to make the hypotenuse tangent and the triangle right-angled with the right angle at
# the inner vertex, the tangential opening (hypotenuse length) must be 2*notch_depth.
# That yields legs length = sqrt(2)*notch_depth.
notch_tangential_opening = 2.0 * notch_depth

# Margins for cutting solids so they are definitely big enough
tangential_margin = 50.0
radial_thickness = radius + 50.0
z_margin = 10.0

# -------------------- BUILD BASE CYLINDER --------------------
base_cyl = Part.makeCylinder(radius, height, Base.Vector(0, 0, 0), Base.Vector(0, 0, 1))
result = base_cyl

# -------------------- BUILD TOP SPHERICAL SURFACE --------------------
sphere = Part.makeSphere(Rc, Base.Vector(0, 0, Rc+Tc))
result = result.cut(sphere)

# ---------------- Facets (top & bottom) - approximate conical chamfer for curved parts ----------------
# Top chamfer: create a conical frustum that spans from z=height-facet_leg..height with radii R-facet_leg .. R
cone_top = Part.makeCone(radius, radius - facet_leg*10, facet_leg*10)
cutter_top = Part.makeCylinder(radius, facet_leg*10)
cutter_top = cutter_top.cut(cone_top)
cutter_top.translate(Base.Vector(0, 0, height - facet_leg))
result = result.cut(cutter_top)

# Bottom chamfer: mirror for bottom
cutter_bot = cutter_top.mirror(Base.Vector(0, 0, facet_leg/2), Base.Vector(0, 0, 1))
result = result.cut(cutter_bot)

# Function to make a bevel cutter box for one flat, bottom or top
def make_cutter_box(theta_deg, rpos, flat_size):
    # Box dimensions: wide enough along tangent, deep enough radially
    box_w = radius - rpos   # tangent length
    box_d = flat_size       # radial length
    box_h = height
    pos = FreeCAD.Vector(rpos, -box_d/2, 0)
    
    box = Part.makeBox(box_w, box_d, box_h, pos)
    
    box.rotate(Base.Vector(0,0,0), Base.Vector(0,0,1), theta_deg)
    return box

# Function to make a bevel cutter box for one flat, bottom or top
def make_bevel_box(theta_deg, rpos, zpos, flat_length):
    # Box dimensions: wide enough along tangent, deep enough radially
    box_w = 40.0   # tangent length
    box_d = flat_length   # radial length
    box_h = facet_leg * 2.0
    
    if zpos < height/2 :
        dir = FreeCAD.Vector(1, 0, -1)
        pos = FreeCAD.Vector(rpos, -box_d/2, zpos + facet_leg)
    else:
        dir = FreeCAD.Vector(1, 0, 1)
        pos = FreeCAD.Vector(rpos - facet_leg, -box_d/2, zpos)
    box = Part.makeBox(box_w, box_d, box_h, pos, dir)
    
    box.rotate(Base.Vector(0,0,0), Base.Vector(0,0,1), theta_deg)
    return box

# -------------------- CREATE FLAT CUTS (FIXED: cut the outside) --------------------
#
cut_shapes = []

for theta_deg in flat_holes_angles_deg:
    box = make_cutter_box(theta_deg, flat_holes_distance_from_center, flat_holes_length)
    cut_shapes.append(box)

for theta_deg in flat_critical_angles_deg:
    box = make_cutter_box(theta_deg, flat_critical_distance_from_center, flat_critical_length)
    cut_shapes.append(box)

# Subtract flats
for i, shp in enumerate(cut_shapes):
    try:
        result = result.cut(shp)
    except Exception as e:
        FreeCAD.Console.PrintError(f"Failed to subtract flat {i} at shape: {e}")

# --- Cut bevels for all 3 critical flats ---
for theta in flat_critical_angles_deg:
    # bottom bevel
    btm_box = make_bevel_box(theta, flat_critical_distance_from_center, 0, flat_critical_length)
    result = result.cut(btm_box)
        
    # top bevel (mirror by shifting z)
    top_box = make_bevel_box(theta, flat_critical_distance_from_center, height, flat_critical_length)
    result = result.cut(top_box)

# -------------------- RADIAL BLIND HOLES --------------------
hole_rpos = flat_holes_distance_from_center
for ang in hole_angles_deg:
    a = math.radians(ang)
    ux = math.cos(a)
    uy = math.sin(a)
    # start point at the nominal outer cylinder surface, at mid-height
    start = Base.Vector(ux * hole_rpos, uy * hole_rpos, Tc / 2.0)
    direction = Base.Vector(-ux, -uy, 0)  # toward center
    # Part.makeCylinder accepts a direction vector; height is hole_depth
    hole = Part.makeCylinder(hole_diameter / 2.0, hole_depth, start, direction)
    try:
        result = result.cut(hole)
    except Exception as e:
        FreeCAD.Console.PrintError(f"Failed to subtract hole at {ang} deg: {e}")

# --- Notches (triangular prisms) ---
for ang_deg in notch_angles:
    ang = math.radians(ang_deg)
    n = Base.Vector(math.cos(ang), math.sin(ang), 0) # radial outward
    t = Base.Vector(-math.sin(ang), math.cos(ang), 0) # tangential

    # Triangle vertices in global coords (center at origin): H1, H2, V
    half_w = notch_tangential_opening / 2.0
    H1 = n * radius + t * (-half_w)
    H2 = n * radius + t * (half_w)
    V = n * (radius - notch_depth)

    wire = Part.makePolygon([H1, V, H2, H1])
    face = Part.Face(wire)
    prism = face.extrude(Base.Vector(0, 0, height))
    result = result.cut(prism)

# -------------------- FINALIZE PART --------------------
final_obj = DOC.addObject("Part::Feature", f"Mirror_{Code}")
final_obj.Shape = result

# Note: the above cone-based chamfer produces an all-around 45° bevel on the curved surface.
# For flats: if you need the facets only along flats' top/bottom edges (and not on the curved areas),
# I can replace the cone-based step with planar chamfers located only at the flat angles — say so and
# I will update.


DOC.recompute()
FreeCAD.Console.PrintMessage("Puck generation completed — flats now remove outside chips, main body preserved.")
