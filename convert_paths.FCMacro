import FreeCAD, FreeCADGui, Part
import ImportSVG  # FreeCAD's built-in SVG parser
import numpy as np
from scipy import optimize
import math

def is_svg_path(obj):
    """Check if object is an SVG import"""
    return hasattr(obj, "PathData") or ("SVG" in obj.TypeId)

def convert_svg_to_shape(obj):
    """Convert SVG path data to FreeCAD edges"""
    return ImportSVG.read(obj.PathData)  # Returns a Compound shape

def fit_circle(points):
    """Fit circle to points using LSM and return center, radius"""
    def calc_R(xc, yc):
        return np.sqrt((points[:,0]-xc)**2 + (points[:,1]-yc)**2)
    
    def f_2(c):
        Ri = calc_R(*c)
        return Ri - Ri.mean()
    
    x = points[:,0]
    y = points[:,1]
    x_m = x.mean()
    y_m = y.mean()
    center_estimate = x_m, y_m
    center, _ = optimize.leastsq(f_2, center_estimate)
    xc, yc = center
    R = calc_R(xc, yc).mean()
    return FreeCAD.Vector(xc, yc, 0), R

def angular_span(points, center):
    """Calculate angular span of points around center (in radians)"""
    angles = []
    for p in points:
        v = p - center
        angles.append(math.atan2(v.y, v.x))
    angles.sort()
    spans = []
    for i in range(len(angles)):
        start = angles[i]
        end = angles[(i+1) % len(angles)]
        span = end - start if end > start else end - start + 2*math.pi
        spans.append(span)
    return max(spans)

def process_svg_object(svg_obj):
    """Convert SVG and return replacement circle/arc"""
    color = svg_obj.ViewObject.LineColor
    width = svg_obj.ViewObject.LineWidth
    
    # Convert SVG to edges
    shape = convert_svg_to_shape(svg_obj)
    if not shape.Edges:
        return None
    
    # Create temporary object for point extraction
    temp_obj = FreeCAD.ActiveDocument.addObject("Part::Feature", "temp")
    temp_obj.Shape = shape
    points = []
    for edge in temp_obj.Shape.Edges:
        points.extend(edge.discretize(Number=100))
    
    # Fit circle/arc (using your original logic)
    # ... [INSERT CIRCLE/ARC FITTING CODE] ...
    # Convert points to numpy array
    pts_array = np.array([(p.x, p.y) for p in points])
    
    # Fit circle using LSM
    center, radius = fit_circle(pts_array)
    
    # Determine if circle or arc
    first_last_dist = points[0].distanceToPoint(points[-1])
    avg_dist = sum(p.distanceToPoint(center) for p in points) / len(points)
    is_circle = first_last_dist < (avg_dist * 0.1)  # 10% threshold
    
    if is_circle:
        # Create circle shape
        circle = Part.Circle()
        circle.Center = center
        circle.Radius = radius
        shape = circle.toShape()
    else:
        # Calculate arc angles
        start_angle = math.atan2(points[0].y - center.y, points[0].x - center.x)
        end_angle = math.atan2(points[-1].y - center.y, points[-1].x - center.x)
        
        # Adjust direction using mid-point
        mid_idx = len(points) // 2
        mid_angle = math.atan2(points[mid_idx].y - center.y, points[mid_idx].x - center.x)
        
        # Reverse if needed (handles clockwise arcs)
        if start_angle > end_angle:
            start_angle, end_angle = end_angle, start_angle
            if not (start_angle <= mid_angle <= end_angle):
                end_angle += 2 * math.pi
        
        # Create arc shape
        circle = Part.Circle()
        circle.Center = center
        circle.Radius = radius
        arc = Part.ArcOfCircle(circle, start_angle, end_angle)
        shape = arc.toShape()
    
    # Create final object
    new_obj = doc.addObject("Part::Feature", "Circle" if is_circle else "Arc")
    new_obj.Shape = shape    
    
    # Cleanup and return
    FreeCAD.ActiveDocument.removeObject(temp_obj.Name)
    return new_obj

def path_to_circle_or_arc():
    doc = FreeCAD.ActiveDocument
    for obj in FreeCADGui.Selection.getSelection():
        if is_svg_path(obj):
            new_obj = process_svg_object(obj)
            if new_obj:
                # Preserve visual properties
                new_obj.ViewObject.LineColor = obj.ViewObject.LineColor
                new_obj.ViewObject.LineWidth = obj.ViewObject.LineWidth
                # Hide original SVG
                obj.ViewObject.Visibility = False
                
path_to_circle_or_arc()
