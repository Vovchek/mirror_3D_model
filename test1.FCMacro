import FreeCAD, Part, math
from FreeCAD import Base

# ========== Test stuff ==========

def check_shape(msg, s):
	print(f"{msg} valid: {s.isValid()}")
	print(f"{msg} type: {s.ShapeType}")

# ========== Surface and Part Parameters ==========
c = 1/773.44    # Curvature [mm⁻¹]
k = -1.0504     # Conic constant
D = 276.41      # Mirror diameter [mm]
ZRS = 140       # Off-axis displacement [mm]
T = 62.13       # Mirror thickness [mm]
Tc = 50.0		# Mirror center thickness [mm]
num_points = 500 # Increased resolution


#================================= Pockets ===============================
# Outer lowering
crown_D = 246.4      # Rear crown diameter
crown_h = 53         # Crown height

# lateral througt holes
D_lat_hole = 7
T_wall = 6 + 4 # +4 to make sure drill through
H_lat_hole = -Tc + 36.73
lat_hole_angles = [150, 60, 300]
lat_hole_shifts = [FreeCAD.Vector(6, 10.39, 0),
                   FreeCAD.Vector(10.39, -6, 0),
                   FreeCAD.Vector(-10.39, -6, 0)]



# ========== Parameters ==========
R_bfs = 799.5          # Best Fit Sphere radius [mm]
pocket_thickness = 6    # Material thickness [mm]
fillet_vertical = 6     # Vertical edge fillet radius [mm]
fillet_ceiling = 2      # Ceiling edge fillet radius [mm]
safety_margin = 10      # Extra extrusion margin [mm]


def robust_fillet(shape, edge_ref, radius, try_alternate=True):
    """
    Create a fillet on a shape with comprehensive error handling
    :param shape: Input shape (Solid or Compound)
    :param edge_ref: Edge reference (index, tag, or edge object)
    :param radius: Fillet radius
    :param try_alternate: Attempt alternate methods if standard fails
    :return: Filleted shape or initial
    """
    doc = App.ActiveDocument
    
    # Method 1: Direct shape operation
    try:
        if isinstance(edge_ref, int):
            # Try by index
            result = shape.makeFillet(radius, [shape.Edges[edge_ref]])
        elif isinstance(edge_ref, Part.Edge):
            # Try by edge object
            result = shape.makeFillet(radius, [edge_ref])
        else:
            # Try by tag
            for edge in shape.Edges:
                if edge.Tag == edge_ref:
                    result = shape.makeFillet(radius, [edge])
                    break
            else:
                raise ValueError("Edge not found by tag")
        
        if result.isValid() and result.Solids:
            return result
    except Exception as e:
        print(f"Direct fillet failed: {str(e)}")
    
    # Method 2: Temporary document objects
    if try_alternate:
        try:
            # Create temporary feature
            temp_name = "TempFilletShape"
            if hasattr(doc, temp_name):
                doc.removeObject(temp_name)
                
            temp_feature = doc.addObject("Part::Feature", temp_name)
            temp_feature.Shape = shape
            doc.recompute()
            
            # Create fillet feature
            fillet = doc.addObject("Part::Fillet", "TempFillet")
            fillet.Base = temp_feature
            
            # Determine edge specification
            if isinstance(edge_ref, int):
                fillet.Edges = [(edge_ref, radius, radius)]
            else:
                # Find edge index by geometry
                for i, edge in enumerate(temp_feature.Shape.Edges):
                    if edge.isSame(edge_ref):
                        fillet.Edges = [(i, radius, radius)]
                        break
                else:
                    raise ValueError("Edge not found in temporary shape")
            
            doc.recompute()
            
            # Validate result
            if fillet.Shape.isValid() and fillet.Shape.Solids:
                result = fillet.Shape.copy()
                
                # Cleanup
                doc.removeObject(fillet.Name)
                doc.removeObject(temp_feature.Name)
                return result
        except Exception as e:
            print(f"Temporary object method failed: {str(e)}")
            # Cleanup if partially created
            for obj_name in ["TempFillet", temp_name]:
                if hasattr(doc, obj_name):
                    doc.removeObject(obj_name)
    
    # Method 3: Manual face-based filleting (advanced)
    if try_alternate:
        print("Attempting face-based filleting...")
        try:
            # Find faces adjacent to edge
            edge = edge_ref if isinstance(edge_ref, Part.Edge) else shape.Edges[edge_ref]
            adjacent_faces = [face for face in shape.Faces if edge in face.Edges]
            
            if len(adjacent_faces) >= 2:
                # Create fillet between faces
                result = shape.makeFillet(radius, [adjacent_faces[0], adjacent_faces[1]])
                if result.isValid():
                    return result
        except Exception as e:
            print(f"Face-based filleting failed: {str(e)}")
    
    return shape  # All methods failed

# ========== Create Pocket Template ==========

def create_triangular_prism(edge_length, side_center, direction, height, safety_margin=10, fillet_radius=6):
    import FreeCAD, Part, math
    from FreeCAD import Base

    # Calculate triangle vertices
    # 1. Find endpoints of the base side
    perp = direction.cross(Base.Vector(0,0,1))  # Perpendicular in XOY
    perp.normalize()
    half_side = edge_length / 2
    p1 = side_center + perp * half_side
    p2 = side_center - perp * half_side

    # 2. Find the opposite vertex
    # The centroid divides the median in a 2:1 ratio from vertex to side
    # For equilateral, distance from side to opposite vertex: h = edge_length * sqrt(3)/2
    h = edge_length * math.sqrt(3) / 2
    p3 = side_center + direction * h

    # 3. Place all points at the same Z (use safety_margin above mirror, extrude downward)
    z0 = safety_margin
    p1 = Base.Vector(p1.x, p1.y, z0)
    p2 = Base.Vector(p2.x, p2.y, z0)
    p3 = Base.Vector(p3.x, p3.y, z0)

    # Create wire and face
    wire = Part.makePolygon([p1, p2, p3, p1])
    face = Part.Face(wire)

    # Extrude downward
    prism = face.extrude(Base.Vector(0, 0, -height))

    if fillet_radius <= 0:
        return prism
    # Fillet vertical edges
    vertical_edges = []
    for edge in prism.Edges:
        v1, v2 = edge.Vertexes
        if abs(v1.Point.x - v2.Point.x) < 1e-6 and abs(v1.Point.y - v2.Point.y) < 1e-6:
            vertical_edges.append(edge)
        elif abs(edge.tangentAt(0).z) > 0.99:
            vertical_edges.append(edge)
    if vertical_edges:
        prism = prism.makeFillet(fillet_radius, vertical_edges)

    return prism

# ========== Create Spherical Ceiling ==========
def create_ceiling_sphere(R_bfs, pocket_thickness):
    R_ceiling = R_bfs + pocket_thickness
    sphere = Part.makeSphere(R_ceiling, Base.Vector(0,0,R_bfs), Base.Vector(0,0,1), -90, -60, 360)
    return sphere

ceiling = create_ceiling_sphere(R_bfs, pocket_thickness)
#Part.show(ceiling, "Ceiling")

# ========== Main Pocket Creation ==========
def create_pocket(edge_length, side_center, direction, height, ceiling, fillet_vertical=6, fillet_ceiling=2):
    prism = create_triangular_prism(edge_length, side_center, direction, height, fillet_radius=fillet_vertical)
    check_shape("prism", prism)
    pocket = prism.cut(ceiling)
    check_shape("pocket", pocket)
    pocket = robust_fillet(pocket, 1, fillet_ceiling)
    return pocket

def angle_between(v1, v2):
    if v1.Length == 0 or v2.Length == 0:
        print("Warning: Zero-length vector in angle calculation.")
        return 0
    dot = v1.normalize().dot(v2.normalize())
    dot = max(min(dot, 1.0), -1.0)
    return math.degrees(math.acos(dot))

def remove_consecutive_duplicates(points):
    """Remove consecutive duplicate points with curvature support"""
    new_points = []
    for point_data in points:
        point, curvature = point_data
        if not new_points or (point - new_points[-1][0]).Length > 1e-6:
            new_points.append((point, curvature))
    return new_points

def create_polygonal_prism(points, height, safety_margin=10, fillet_radius=6):
    """
    Create a polygonal prism with arc segments
    :param points: List of tuples (Base.Vector, curvature)
                   curvature = 0 for straight segments, >0 for arc radius
    :param height: Height of the prism
    :param safety_margin: Z-offset for the base
    :param fillet_radius: Fillet radius for vertical edges
    :return: Part.Shape
    """
    # Process points and remove duplicates
    points = remove_consecutive_duplicates(points)
    
    # Raise all points to the same Z (safety_margin above surface)
    base_points = [(Base.Vector(p.x, p.y, safety_margin), c) for p, c in points]
    
    # Close the polygon if not closed
    if len(base_points) > 0 and (base_points[0][0] - base_points[-1][0]).Length > 1e-6:
        base_points.append(base_points[0])
    
    # Create edges with arcs where curvature > 0
    edges = []
    n = len(base_points)
    for i in range(n - 1):
        start, start_curvature = base_points[i]
        end, end_curvature = base_points[i + 1]
        
        # Use curvature from the starting point
        curvature = start_curvature
        
        if abs(curvature) < 1e-6:  # Straight segment
            edges.append(Part.LineSegment(start, end).toShape())
        else:  # Arc segment
            chord_vec = end - start
            chord_length = chord_vec.Length
            
            # Validate curvature radius
            if abs(curvature) < chord_length / 2:
                print(f"Warning: Curvature radius {curvature} too small for chord length {chord_length:.2f}")
                edges.append(Part.LineSegment(start, end).toShape())
                continue
                
            # Calculate perpendicular direction
            chord_dir = chord_vec.normalize()
            perp = chord_dir.cross(Base.Vector(0, 0, 1))
            perp.normalize()
            
            # Calculate center and midpoint for arc
            mid = (start + end) * 0.5
            d = math.sqrt(curvature**2 - (chord_length/2)**2)
            
            # Determine bulge direction based on curvature sign
            sign = 1.0 if curvature > 0 else -1.0
            center = mid + perp * d * sign
            
            # Create arc through three points
            try:
                # Get vectors from center to start and end
                v1 = start - center
                v2 = end - center
                v1.normalize()
                v2.normalize()
                
                # Calculate arc midpoint
                arc_mid_dir = (v1 + v2).normalize()
                arc_mid = center + arc_mid_dir * abs(curvature)
                
                # Create the arc
                arc = Part.Arc(start, arc_mid, end)
                edges.append(arc.toShape())
            except Exception as e:
                print(f"Arc creation failed: {str(e)}")
                edges.append(Part.LineSegment(start, end).toShape())
    
    # Create wire and face
    wire = Part.Wire(edges)
    face = Part.Face(wire)
    
    # Extrude downward to create prism
    prism = face.extrude(Base.Vector(0, 0, -height))

    # Fillet vertical edges (same as before)
    if fillet_radius > 0:
        vertical_edges = []
        for edge in prism.Edges:
            v1, v2 = edge.Vertexes
            if (abs(v1.Point.x - v2.Point.x) < 1e-6 and
                abs(v1.Point.y - v2.Point.y) < 1e-6 and
                abs(v1.Point.z - v2.Point.z) > 1e-6):
                vertical_edges.append(edge)
        
        if vertical_edges:
            try:
                prism = prism.makeFillet(fillet_radius, vertical_edges)
            except Exception as e:
                print(f"Vertical fillet failed: {str(e)}")
    
    return prism

def create_polygonal_pocket(points, height, ceiling, safety_margin=10, fillet_radius=6, fillet_ceiling=2):
    prism = create_polygonal_prism(points, height, safety_margin, fillet_radius)
    pocket = prism.cut(ceiling)
    pocket = robust_fillet(pocket, 0, fillet_ceiling)
    return pocket

def mirror_shape_about_plane(shape, angle_deg, plane_point=Base.Vector(0,0,0)):
    """
    Mirrors a shape about a plane containing the OZ axis and making angle_deg with OX axis.
    :param shape: The FreeCAD shape to mirror (e.g., Part.Shape, Part.Solid, etc.)
    :param angle_deg: Angle (degrees) between OX and the plane (counterclockwise in XOY)
    :param plane_point: A point on the mirror plane (default: origin)
    :return: Mirrored shape (new object)
    """
    # Compute normal vector for the plane
    angle_rad = math.radians(angle_deg)
    # The plane's normal is perpendicular to the plane; for a plane containing OZ and at angle with OX,
    # the normal is in the XOY plane, at angle + 90° from OX.
    normal = Base.Vector(math.sin(angle_rad), -math.cos(angle_rad), 0)  # normal in XOY
    # Mirror the shape
    mirrored = shape.mirror(plane_point, normal)
    return mirrored

final_mirror = Part.makeCylinder(D/2, T, FreeCAD.Vector(0, 0, -Tc))
pockets = []


# ========== Create 3 small triangular Pockets ==========
edge_length = 62.5      # Triangle side length [mm]
radial_pos = 115.2      # Distance from center to nearest vertex [mm]
triangle_height = edge_length*math.cos(math.radians(30))
angles = (0, 120, 240)  # 0°, 120°, 240°
"""
pocket = create_pocket(edge_length, Base.Vector(radial_pos, 0, 0), Base.Vector(-1, 0, 0), Tc+2*safety_margin, ceiling, 0)
#edges = [pocket.Edges[i] for i in [0,1,11,10,9,6,5]]
#pocket = pocket.makeFillet(fillet_ceiling, edges)

pockets.append(pocket)
Part.show(pocket, f"pocket_0")
final_mirror = final_mirror.cut(pocket)

pocket.rotate(Base.Vector(0,0,0), Base.Vector(0,0,1), 120)
check_shape("pocket_120", pocket)
pockets.append(pocket)
Part.show(pocket, f"pocket_120")
final_mirror = final_mirror.cut(pocket)

pocket.rotate(Base.Vector(0,0,0), Base.Vector(0,0,1), 120)
check_shape("pocket_240", pocket)
pockets.append(pocket)
Part.show(pocket, f"pocket_240")
final_mirror = final_mirror.cut(pocket)

# ========== Create 3 bigger triangular Pockets ==========
edge_length = 85      # Triangle side length [mm]
radial_pos = -30.5      # Distance from center to nearest vertex [mm]
angles = (0, 120, 240)  # 0°, 120°, 240°

pocket = create_pocket(edge_length, Base.Vector(radial_pos, 0, 0), Base.Vector(-1, 0, 0), Tc+2*safety_margin, ceiling)
pockets.append(pocket)
Part.show(pocket, f"big_pocket_0")
final_mirror = final_mirror.cut(pocket)

pocket.rotate(Base.Vector(0,0,0), Base.Vector(0,0,1), 120)
check_shape("big_pocket_120", pocket)
pockets.append(pocket)
Part.show(pocket, f"big_pocket_120")
final_mirror = final_mirror.cut(pocket)

pocket.rotate(Base.Vector(0,0,0), Base.Vector(0,0,1), 120)
check_shape("big_pocket_240", pocket)
pockets.append(pocket)
Part.show(pocket, f"big_pocket_240")
final_mirror = final_mirror.cut(pocket)


# ========== Create 1 center triangular Pocket ==========

radial_pos = -24.5      # Distance from center to nearest vertex [mm]
pocket = create_pocket(edge_length, Base.Vector(radial_pos, 0, 0), Base.Vector(1, 0, 0), Tc+2*safety_margin, ceiling)
pockets.append(pocket)
Part.show(pocket, f"center_pocket")
final_mirror = final_mirror.cut(pocket)
"""
# ========== Create Polygonal Pockets ==========
polygon_points = [
    (Base.Vector(58, 5, 0), 0),
    (Base.Vector(58, 99, 0), 0),
    (Base.Vector(76, 89, 0), 117.03),
    (Base.Vector(89, 76, 0), 0),
    (Base.Vector(112.5, 35.8, 0), 0)
]

height = Tc + 2*safety_margin  # Use your mirror thickness and margin

pocket = create_polygonal_pocket(polygon_points, height, ceiling)
Part.show(pocket, "poly_1")
"""
final_mirror = final_mirror.cut(pocket)

pocket = mirror_shape_about_plane(pocket, 0)
Part.show(pocket, "poly_2")
final_mirror = final_mirror.cut(pocket)

pocket = mirror_shape_about_plane(pocket, -60)
Part.show(pocket, "poly_3")
final_mirror = final_mirror.cut(pocket)

pocket = mirror_shape_about_plane(pocket, 60)
Part.show(pocket, "poly_4")
final_mirror = final_mirror.cut(pocket)

pocket = mirror_shape_about_plane(pocket, 0)
Part.show(pocket, "poly_5")
final_mirror = final_mirror.cut(pocket)

pocket = mirror_shape_about_plane(pocket, -60)
Part.show(pocket, "poly_6")
final_mirror = final_mirror.cut(pocket)

# ========== Mounting holes ================

hole_diameter = 15
hole_position_x = 55

# Create cylindrical pocket (extruded circle)
# Place pocket top at safety margin above mirror surface (Z= safety_margin)
pocket_top_z = safety_margin
depth = Tc + 2 * safety_margin
pocket_base_z = pocket_top_z - depth

hole = Part.makeCylinder(hole_diameter/2.0, depth, Base.Vector(hole_position_x, 0, pocket_base_z))
hole_cut = hole.cut(ceiling)
#print(f"hole: {hole}")
hole = robust_fillet(hole_cut, 1, fillet_ceiling)
#print(f"hole: {hole}")
Part.show(hole, f"hole_0")
final_mirror = final_mirror.cut(hole)
#
hole.rotate(Base.Vector(0,0,0), Base.Vector(0,0,1), 120)
final_mirror = final_mirror.cut(hole)
Part.show(hole, f"hole_120")

hole.rotate(Base.Vector(0,0,0), Base.Vector(0,0,1), 120)
final_mirror = final_mirror.cut(hole)
Part.show(hole, f"hole_240")

# ========== Drill lateral holes ===========
lat_hole = Part.makeCylinder(D_lat_hole/2.0, T_wall, Base.Vector(crown_D/2.0 + 1, 0, H_lat_hole), Base.Vector(-1, 0, 0))
Part.show(lat_hole, f"initial_hole")

for i in range(3):
    hole = Part.makeCylinder(D_lat_hole/2.0, T_wall, Base.Vector(crown_D/2.0 + 1, 0, H_lat_hole), Base.Vector(-1, 0, 0))
    hole.rotate(Base.Vector(0,0,0), Base.Vector(0,0,1), lat_hole_angles[i])
    hole.translate(lat_hole_shifts[i])
    Part.show(hole, f"lat_hole_{lat_hole_angles[i]}")
    final_mirror = final_mirror.cut(hole)

# ========== Finalize and Display ==========
Part.show(final_mirror, "MirrorWithPockets")


#================================= Section to check geometry ===============================
def create_section(body, slice_size, slice_position, slice_dirZ):
    if slice_size <= 0:
	    print("zero slice size")
	    return None
    # If mirror_body is a Compound, extract its solids
    solids = [s for s in body.Solids]

# Create the XOZ plane as before
    slice_plane = Part.makePlane(slice_size, slice_size, slice_position, slice_dirZ)

# Section each solid in the compound
    sections = []
    for solid in solids:
        section = solid.section(slice_plane)
        if not section.isNull():
            sections.append(section)

    if sections:  # Only if the list is not empty
        compound_section = Part.Compound(sections)
        print("section created")
        return compound_section
    print("no solids found")

slice_dirZ = FreeCAD.Vector(0, 1, 0) 
slice_size = 1000
slice_position = FreeCAD.Vector(-slice_size/2.0, 0, -slice_size/2.0)
    
section = create_section(final_mirror, slice_size, slice_position, slice_dirZ)
if not (section is None):
    Part.show(section, "section")
"""

App.ActiveDocument.recompute()
