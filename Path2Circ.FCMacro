import FreeCAD, FreeCADGui, Part
import numpy as np
from scipy import optimize
import math
import time  # For performance measurement

def fit_circle(points):
    """Fit circle to points using LSM and return center, radius"""
    def calc_R(xc, yc):
        return np.sqrt((points[:,0]-xc)**2 + (points[:,1]-yc)**2)
    
    def f_2(c):
        Ri = calc_R(*c)
        return Ri - Ri.mean()
    
    x = points[:,0]
    y = points[:,1]
    x_m = x.mean()
    y_m = y.mean()
    center_estimate = x_m, y_m
    center, _ = optimize.leastsq(f_2, center_estimate)
    xc, yc = center
    R = calc_R(xc, yc).mean()
    return FreeCAD.Vector(xc, yc, 0), R

def is_convertible_path(obj):
    """Check if object can be converted to circle/arc"""
    if hasattr(obj, "PathData") or ("SVG" in obj.TypeId):
        return True
    if hasattr(obj, 'Shape') and obj.Shape:
        return obj.Shape.ShapeType in ["Wire", "Edge", "Compound"]
    return False

def get_path_points(obj):
    """Extract points from various path types"""
    points = []
    if hasattr(obj, "PathData"):
        try:
            shape = Part.Shape()
            shape.importSVG(obj.PathData)
            for edge in shape.Edges:
                points.extend(edge.discretize(Number=20))
        except:
            print("Failed to convert SVG path")
    elif hasattr(obj, 'Shape') and obj.Shape:
        shape = obj.Shape
        if shape.ShapeType == "Wire":
            for edge in shape.Edges:
                points.extend(edge.discretize(Number=20))
        elif shape.ShapeType == "Edge":
            points.extend(shape.discretize(Number=20))
        elif shape.ShapeType == "Compound":
            for sub_shape in shape.SubShapes:
                if sub_shape.ShapeType == "Edge":
                    points.extend(sub_shape.discretize(Number=20))
                elif sub_shape.ShapeType == "Wire":
                    for edge in sub_shape.Edges:
                        points.extend(edge.discretize(Number=20))
    return points

def is_closed_curve(points, center, radius, threshold=0.05):
    """Fast circle detection using critical points"""
    # Quick endpoint check
    if points[0].distanceToPoint(points[-1]) > radius * threshold:
        return False
    
    # Check critical points
    critical_points = [
        points[0],
        points[len(points)//2],
        points[-1]
    ]
    
    critical_dists = [p.distanceToPoint(center) for p in critical_points]
    max_dev = max(abs(dist - radius) for dist in critical_dists)
    
    return max_dev < radius * threshold

def path_to_circle_or_arc():
    doc = FreeCAD.ActiveDocument
    if not doc: return
    
    for obj in FreeCADGui.Selection.getSelection():
        start_time = time.time()
        print(f"\nProcessing: {obj.Label} ({obj.TypeId})")
        
        if not is_convertible_path(obj):
            print("Skipping non-convertible object")
            continue
            
        points = get_path_points(obj)
        if len(points) < 10:
            print(f"Only {len(points)} points - skipping")
            continue
            
        # Convert to numpy array
        pts_array = np.array([(p.x, p.y) for p in points])
        
        # Fit circle
        try:
            fit_start = time.time()
            center, radius = fit_circle(pts_array)
            print(f"Circle fit: {time.time()-fit_start:.2f}s")
        except Exception as e:
            print(f"Fitting failed: {str(e)}")
            continue
        
        # FAST circle detection
        detect_start = time.time()
        is_circle = is_closed_curve(points, center, radius)
        print(f"Circle detection: {time.time()-detect_start:.4f}s")
        
        if is_circle:
            # Create circle
            circle = Part.Circle()
            circle.Center = center
            circle.Radius = radius
            shape = circle.toShape()
            obj_name = "Circle"
        else:
            # Create arc
            start_angle = math.atan2(points[0].y - center.y, points[0].x - center.x)
            end_angle = math.atan2(points[-1].y - center.y, points[-1].x - center.x)
            
            circle = Part.Circle()
            circle.Center = center
            circle.Radius = radius
            arc = Part.ArcOfCircle(circle, start_angle, end_angle)
            shape = arc.toShape()
            obj_name = "Arc"
        
        # Create object
        new_obj = doc.addObject("Part::Feature", obj_name)
        new_obj.Shape = shape
        
        # IMPROVE DISPLAY QUALITY
        if is_circle:
            # Smoother circle display
            new_obj.ViewObject.AngularDeflection = 0.1  # Finer resolution
            new_obj.ViewObject.Deviation = 0.01  # Smaller tolerance
        else:
            # Good enough for arcs
            new_obj.ViewObject.AngularDeflection = 1.0
        
        # Preserve appearance
        if hasattr(obj, 'ViewObject'):
            new_obj.ViewObject.LineColor = obj.ViewObject.LineColor
            new_obj.ViewObject.LineWidth = obj.ViewObject.LineWidth
            new_obj.ViewObject.AngularDeflection = 0.1  # Default=0.4
            new_obj.ViewObject.Deviation = 0.01         # Default=0.5
            obj.ViewObject.Visibility = False
        
        print(f"Created {obj_name} in {time.time()-start_time:.2f}s")
    
    print("Processing complete")
    doc.recompute()

# Run the script
path_to_circle_or_arc()
